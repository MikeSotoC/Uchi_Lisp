;;; UCHI Expediente técnico (resumen base)

(defun uchi:exp-file-status (name)
  (if (findfile (strcat (uchi:launcher-dir-safe) "/" name)) "OK" "FALTA")
)

(defun uchi:exp-required-files ()
  (list
    (list "TOPO" "uchi_surface.xml")
    (list "TOPO" "uchi_report.txt")
    (list "TOPO" "uchi_qa_cad_matrix.csv")
    (list "URBANISMO" "uchi_subdivision.csv")
    (list "URBANISMO" "uchi_subdivision_summary.csv")
    (list "REDES" "uchi_redes.csv")
    (list "REDES" "uchi_interferencias.csv")
    (list "HIDRAULICA" "uchi_hidraulica.csv")
    (list "HIDRAULICA" "uchi_hidraulica_tramos.csv")
    (list "VIAL" "uchi_pavimentos.csv")
    (list "VIAL" "uchi_carretera_norma.csv")
    (list "QA" "uchi_expediente_normativa.csv")
  )
)

(defun uchi:exp-write-normativa-csv (/ path fp st)
  (setq path (strcat (uchi:launcher-dir-safe) "/uchi_expediente_normativa.csv"))
  (setq fp (open path "w"))
  (if fp
    (progn
      (write-line "modulo,indicador,valor,estado" fp)
      (setq st (if (= (vl-princ-to-string (uchi:project-get "drain_norm_ok")) "0") "OBSERVAR" "OK"))
      (write-line (strcat "DRENAJE,drain_norm_ok," (vl-princ-to-string (uchi:project-get "drain_norm_ok")) "," st) fp)
      (setq st (if (= (vl-princ-to-string (uchi:project-get "redes_norm_ok")) "0") "OBSERVAR" "OK"))
      (write-line (strcat "REDES,redes_norm_ok," (vl-princ-to-string (uchi:project-get "redes_norm_ok")) "," st) fp)
      (setq st (if (= (vl-princ-to-string (uchi:project-get "hid_tramos_vel_ok")) "0") "OBSERVAR" "OK"))
      (write-line (strcat "HIDRAULICA,hid_tramos_vel_ok," (vl-princ-to-string (uchi:project-get "hid_tramos_vel_ok")) "," st) fp)
      (setq st (if (= (vl-princ-to-string (uchi:project-get "pav_norm_ok")) "SI") "OK" "OBSERVAR"))
      (write-line (strcat "PAVIMENTOS,pav_norm_ok," (vl-princ-to-string (uchi:project-get "pav_norm_ok")) "," st) fp)
      (setq st (if (= (vl-princ-to-string (uchi:project-get "road_norm_ok")) "SI") "OK" "OBSERVAR"))
      (write-line (strcat "CARRETERA,road_norm_ok," (vl-princ-to-string (uchi:project-get "road_norm_ok")) "," st) fp)
      (setq st (if (= (vl-princ-to-string (uchi:project-get "qc_ok")) "1") "OK" "OBSERVAR"))
      (write-line (strcat "QA,qc_ok," (vl-princ-to-string (uchi:project-get "qc_ok")) "," st) fp)
      (close fp)
    )
  )
)

(defun uchi:exp-write-disc-csv (/ path fp)
  (setq path (strcat (uchi:launcher-dir-safe) "/uchi_expediente_cuadros.csv"))
  (setq fp (open path "w"))
  (if fp
    (progn
      (write-line "disciplina,archivo,estado" fp)
      (foreach it (uchi:exp-required-files)
        (write-line (strcat (car it) "," (cadr it) "," (uchi:exp-file-status (cadr it))) fp)
      )
      (close fp)
    )
  )
)

(defun uchi:exp-write-final-csv (/ path fp ok total it)
  (setq path (strcat (uchi:launcher-dir-safe) "/uchi_expediente_final.csv"))
  (setq fp (open path "w"))
  (setq ok 0 total 0)
  (if fp
    (progn
      (write-line "bloque,item,estado,detalle" fp)
      (write-line (strcat "RESUMEN,proyecto,OK," (uchi:project-get "name")) fp)
      (write-line (strcat "RESUMEN,points_count,OK," (vl-princ-to-string (uchi:project-get "points_count"))) fp)
      (write-line (strcat "RESUMEN,tin_triangles,OK," (vl-princ-to-string (uchi:project-get "tin_triangles"))) fp)
      (write-line (strcat "RESUMEN,qc_ok,OK," (vl-princ-to-string (uchi:project-get "qc_ok"))) fp)
      (foreach it (uchi:exp-required-files)
        (setq total (+ total 1))
        (if (= (uchi:exp-file-status (cadr it)) "OK") (setq ok (+ ok 1)))
        (write-line
          (strcat "ENTREGABLE," (cadr it) "," (uchi:exp-file-status (cadr it)) "," (car it))
          fp
        )
      )
      (write-line (strcat "RESUMEN,entregables_ok,OK," (itoa ok) "/" (itoa total)) fp)
      (write-line (strcat "RESUMEN,estado_expediente," (if (= ok total) "OK" "INCOMPLETO")
                          "," (if (= ok total) "LISTO_PARA_RELEASE" "REVISAR_FALTANTES")) fp)
      (close fp)
    )
  )
)

(defun C:UCHI_EXPEDIENTE (/ path fp)
  (uchi:topo-init)
  (if (fboundp 'uchi:qa-matrix-export) (uchi:qa-matrix-export))
  (setq path (strcat (uchi:launcher-dir-safe) "/uchi_expediente.txt"))
  (setq fp (open path "w"))
  (if fp
    (progn
      (write-line "UCHI - Expediente técnico (resumen automático)" fp)
      (write-line "============================================" fp)
      (write-line (strcat "Proyecto: " (uchi:project-get "name")) fp)
      (write-line (strcat "Puntos: " (vl-princ-to-string (uchi:project-get "points_count"))) fp)
      (write-line (strcat "TIN triángulos: " (vl-princ-to-string (uchi:project-get "tin_triangles"))) fp)
      (write-line (strcat "Subdivisión lotes: " (vl-princ-to-string (uchi:project-get "subdivision_lots"))) fp)
      (write-line (strcat "Volumen corte: " (vl-princ-to-string (uchi:project-get "cut"))) fp)
      (write-line (strcat "Volumen relleno: " (vl-princ-to-string (uchi:project-get "fill"))) fp)
      (write-line (strcat "Interferencias: " (vl-princ-to-string (uchi:project-get "interf_count"))) fp)
      (write-line "Archivos de expediente:" fp)
      (foreach it (uchi:exp-required-files)
        (write-line (strcat "- " (cadr it) ": " (uchi:exp-file-status (cadr it))) fp)
      )
      (write-line "Cuadros por disciplina: uchi_expediente_cuadros.csv" fp)
      (write-line "Consolidado final: uchi_expediente_final.csv" fp)
      (write-line "Chequeo normativo: uchi_expediente_normativa.csv" fp)
      (close fp)
      (uchi:exp-write-normativa-csv)
      (uchi:exp-write-disc-csv)
      (uchi:exp-write-final-csv)
      (uchi:log "Expediente técnico generado: txt + cuadros + normativa + final")
    )
    (uchi:log "ERROR al generar expediente.")
  )
  (princ)
)

(princ)
