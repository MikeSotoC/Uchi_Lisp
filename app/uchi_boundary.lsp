;;; UCHI Boundary / breakline base

(setq *uchi-boundary* nil)
(setq *uchi-boundary-holes* nil)

(defun uchi:cross2d (o a b)
  (- (* (- (cadr a) (cadr o)) (- (caddr b) (caddr o)))
     (* (- (caddr a) (caddr o)) (- (cadr b) (cadr o))))
)

(defun uchi:points-xy-sorted ()
  (vl-sort *uchi-points* '(lambda (a b) (if (= (cadr a) (cadr b)) (< (caddr a) (caddr b)) (< (cadr a) (cadr b)))))
)

(defun uchi:convex-hull (pts / lower upper p)
  (setq lower nil upper nil)
  (foreach p pts
    (while (and (>= (length lower) 2)
                (<= (uchi:cross2d (nth (- (length lower) 2) lower) (nth (- (length lower) 1) lower) p) 0.0))
      (setq lower (reverse (cdr (reverse lower))))
    )
    (setq lower (append lower (list p)))
  )
  (foreach p (reverse pts)
    (while (and (>= (length upper) 2)
                (<= (uchi:cross2d (nth (- (length upper) 2) upper) (nth (- (length upper) 1) upper) p) 0.0))
      (setq upper (reverse (cdr (reverse upper))))
    )
    (setq upper (append upper (list p)))
  )
  (append (reverse (cdr (reverse lower))) (reverse (cdr (reverse upper))))
)

(defun uchi:boundary-point-in-poly (pt poly / inside i j pi pj xi yi xj yj px py)
  (setq inside nil)
  (setq px (car pt) py (cadr pt))
  (setq i 0 j (- (length poly) 1))
  (while (< i (length poly))
    (setq pi (nth i poly) pj (nth j poly))
    (setq xi (car pi) yi (cadr pi) xj (car pj) yj (cadr pj))
    (if (and (/= yi yj)
             (/= (> yi py) (> yj py))
             (< px (+ xi (* (/ (- py yi) (- yj yi)) (- xj xi)))))
      (setq inside (not inside))
    )
    (setq j i i (+ i 1))
  )
  inside
)

(defun uchi:boundary-point-in-scope (pt / inout hole inside-hole)
  (setq inout (if (and *uchi-boundary* (> (length *uchi-boundary*) 2))
                (uchi:boundary-point-in-poly pt *uchi-boundary*)
                T))
  (setq inside-hole nil)
  (foreach hole *uchi-boundary-holes*
    (if (and (> (length hole) 2) (uchi:boundary-point-in-poly pt hole))
      (setq inside-hole T)
    )
  )
  (and inout (not inside-hole))
)

(defun uchi:boundary-read-outer-csv (path / out cols line)
  (setq out nil)
  (foreach line (uchi:read-lines path)
    (setq cols (uchi:split-csv-line line))
    (if (>= (length cols) 2)
      (setq out (append out (list (list (uchi:to-real (nth 0 cols))
                                        (uchi:to-real (nth 1 cols))))))
    )
  )
  out
)

(defun uchi:boundary-read-holes-csv (path / groups line cols hid p g)
  ;; Formato: hole_id,x,y
  (setq groups nil)
  (foreach line (uchi:read-lines path)
    (setq cols (uchi:split-csv-line line))
    (if (>= (length cols) 3)
      (progn
        (setq hid (nth 0 cols))
        (setq p (list (uchi:to-real (nth 1 cols)) (uchi:to-real (nth 2 cols))))
        (setq g (assoc hid groups))
        (if g
          (setq groups (subst (cons hid (append (cdr g) (list p))) g groups))
          (setq groups (append groups (list (cons hid (list p)))))
        )
      )
    )
  )
  (mapcar 'cdr groups)
)

(defun uchi:boundary-draw ()
  (if (and *uchi-boundary* (> (length *uchi-boundary*) 2))
    (uchi:draw-polyline-2d (append *uchi-boundary* (list (car *uchi-boundary*))) "UCHI_BOUNDARY")
  )
  (foreach h *uchi-boundary-holes*
    (if (> (length h) 2)
      (uchi:draw-polyline-2d (append h (list (car h))) "UCHI_BOUNDARY_HOLE")
    )
  )
)

(defun C:UCHI_BOUNDARY (/ fouter fholes)
  (uchi:topo-init)
  (if (> (length *uchi-points*) 2)
    (progn
      (setq fouter (getenv "UCHI_CFG_BOUNDARY_CSV"))
      (setq fholes (getenv "UCHI_CFG_BOUNDARY_HOLES_CSV"))
      (if (and fouter (/= fouter "") (findfile fouter))
        (setq *uchi-boundary* (uchi:boundary-read-outer-csv fouter))
        (setq *uchi-boundary* (mapcar '(lambda (p) (list (cadr p) (caddr p))) (uchi:convex-hull (uchi:points-xy-sorted))))
      )
      (if (and fholes (/= fholes "") (findfile fholes))
        (setq *uchi-boundary-holes* (uchi:boundary-read-holes-csv fholes))
        (setq *uchi-boundary-holes* nil)
      )
      (uchi:project-set "boundary_vertices" (length *uchi-boundary*))
      (uchi:project-set "boundary_holes" (length *uchi-boundary-holes*))
      (uchi:project-save)
      (uchi:boundary-draw)
      (uchi:log (strcat "Boundary generada. Vértices=" (itoa (length *uchi-boundary*))
                        ", huecos=" (itoa (length *uchi-boundary-holes*))))
    )
    (uchi:log "Boundary: se requieren al menos 3 puntos válidos.")
  )
  (princ)
)

(princ)
