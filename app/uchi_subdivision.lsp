;;; UCHI Subdivisión (urbana/rural configurable)

(defun uchi:subdiv-cols () (max 1 (atoi (vl-princ-to-string (or (getenv "UCHI_CFG_SUBDIV_COLS") 4)))))
(defun uchi:subdiv-rows () (max 1 (atoi (vl-princ-to-string (or (getenv "UCHI_CFG_SUBDIV_ROWS") 4)))))
(defun uchi:subdiv-ndiv () (max 0 (atoi (vl-princ-to-string (or (getenv "UCHI_CFG_SUBDIV_NDIV") 0)))))
(defun uchi:subdiv-prefix () (or (getenv "UCHI_CFG_SUBDIV_PREFIX") "SUB"))
(defun uchi:subdiv-road-every () (max 0 (atoi (vl-princ-to-string (or (getenv "UCHI_CFG_SUBDIV_ROAD_EVERY") 3)))))
(defun uchi:subdiv-min-area () (max 1.0 (uchi:to-real (or (getenv "UCHI_CFG_SUBDIV_MIN_AREA") 80.0))))
(defun uchi:subdiv-road-angle-deg () (uchi:to-real (or (getenv "UCHI_CFG_SUBDIV_ROAD_ANGLE") 0.0)))
(defun uchi:subdiv-min-front () (max 1.0 (uchi:to-real (or (getenv "UCHI_CFG_SUBDIV_MIN_FRONT") 6.0))))
(defun uchi:subdiv-aporte-pct () (max 0.0 (uchi:to-real (or (getenv "UCHI_CFG_SUBDIV_APORTE_PCT") 0.0))))

(defun uchi:subdiv-annotate (pt txt)
  (if (fboundp 'uchi:draw-text)
    (uchi:draw-text (list (car pt) (cadr pt) 0.0) 0.9 txt "UCHI_SUBDIV")
  )
)

(defun uchi:ceil (x / i)
  (setq i (fix x))
  (if (> x i) (+ i 1) i)
)

(defun uchi:subdiv-export-csv (rows / path fp r)
  (setq path (strcat (uchi:launcher-dir-safe) "/uchi_subdivision.csv"))
  (setq fp (open path "w"))
  (if fp
    (progn
      (write-line "id,type,row,col,xmin,ymin,xmax,ymax,area" fp)
      (foreach r rows
        (write-line
          (strcat (car r) "," (cadr r) "," (itoa (caddr r)) "," (itoa (nth 3 r)) ","
                  (rtos (nth 4 r) 2 3) "," (rtos (nth 5 r) 2 3) ","
                  (rtos (nth 6 r) 2 3) "," (rtos (nth 7 r) 2 3) "," (rtos (nth 8 r) 2 2))
          fp
        )
      )
      (close fp)
      path
    )
    nil
  )
)

(defun uchi:subdiv-export-summary (tot lot road aporte / path fp)
  (setq path (strcat (uchi:launcher-dir-safe) "/uchi_subdivision_summary.csv"))
  (setq fp (open path "w"))
  (if fp
    (progn
      (write-line "metric,value" fp)
      (write-line (strcat "area_total," (rtos tot 2 2)) fp)
      (write-line (strcat "area_lotes," (rtos lot 2 2)) fp)
      (write-line (strcat "area_vias," (rtos road 2 2)) fp)
      (write-line (strcat "area_aportes," (rtos aporte 2 2)) fp)
      (close fp)
    )
  )
)

(defun uchi:subdiv-cell-inside-p (x1 y1 x2 y2 / cx cy)
  (setq cx (/ (+ x1 x2) 2.0) cy (/ (+ y1 y2) 2.0))
  (if (and *uchi-boundary* (> (length *uchi-boundary*) 2))
    (uchi:boundary-point-in-poly (list cx cy) *uchi-boundary*)
    T
  )
)

(defun uchi:subdiv-draw-oriented-road-guides (xmin xmax ymin ymax spacing / ang ux uy nx ny cx cy t p1 p2 limit)
  (setq ang (* pi (/ (uchi:subdiv-road-angle-deg) 180.0)))
  (setq ux (cos ang) uy (sin ang))
  (setq nx (- uy) ny ux)
  (setq cx (/ (+ xmin xmax) 2.0) cy (/ (+ ymin ymax) 2.0))
  (setq limit (+ (- xmax xmin) (- ymax ymin)))
  (setq t (- limit))
  (while (<= t limit)
    (setq p1 (list (+ (+ cx (* t nx)) (* (- limit) ux)) (+ (+ cy (* t ny)) (* (- limit) uy)) 0.0))
    (setq p2 (list (+ (+ cx (* t nx)) (* limit ux)) (+ (+ cy (* t ny)) (* limit uy)) 0.0))
    (uchi:draw-line p1 p2 "UCHI_ROAD")
    (setq t (+ t spacing))
  )
)

(defun C:UCHI_SUBDIVISION (/ st xmin xmax ymin ymax cols rows ndiv dx dy r c x1 y1 x2 y2 id out area roadn isroad cx cy lotcount
                             front aporteTarget aporteAcc areaTot areaLot areaRoad areaAporte isCorner)
  (uchi:topo-init)
  (if (> (length *uchi-points*) 2)
    (progn
      (if (fboundp 'C:UCHI_BOUNDARY) (C:UCHI_BOUNDARY))
      (setq st (uchi:surface-stats))
      (setq xmin (cdr (assoc "xmin" st)) xmax (cdr (assoc "xmax" st)))
      (setq ymin (cdr (assoc "ymin" st)) ymax (cdr (assoc "ymax" st)))
      (setq cols (uchi:subdiv-cols) rows (uchi:subdiv-rows) ndiv (uchi:subdiv-ndiv))
      (if (> ndiv 0)
        (progn
          (setq cols (max 1 (uchi:ceil (sqrt ndiv))))
          (setq rows (max 1 (uchi:ceil (/ ndiv cols))))
        )
      )
      (setq roadn (uchi:subdiv-road-every))
      (setq dx (/ (- xmax xmin) cols))
      (setq dy (/ (- ymax ymin) rows))
      (setq front (min dx dy))
      (setq areaTot (* (- xmax xmin) (- ymax ymin)))
      (setq aporteTarget (* areaTot (/ (uchi:subdiv-aporte-pct) 100.0)))
      (setq aporteAcc 0.0 areaLot 0.0 areaRoad 0.0 areaAporte 0.0)
      (setq r 0 out nil lotcount 0)
      (while (< r rows)
        (setq c 0)
        (while (< c cols)
          (setq x1 (+ xmin (* c dx)) y1 (+ ymin (* r dy)))
          (setq x2 (+ xmin (* (+ c 1) dx)) y2 (+ ymin (* (+ r 1) dy)))
          (setq area (* (- x2 x1) (- y2 y1)))
          (setq isroad (and (> roadn 0) (or (= (rem (+ c 1) roadn) 0) (= (rem (+ r 1) roadn) 0))))
          (setq isCorner (and (> roadn 0) (= (rem (+ c 1) roadn) 1) (= (rem (+ r 1) roadn) 1)))
          (if (and (uchi:subdiv-cell-inside-p x1 y1 x2 y2) (>= area (uchi:subdiv-min-area)))
            (progn
              (if isroad
                (progn
                  (uchi:draw-polyline-2d (list (list x1 y1) (list x2 y1) (list x2 y2) (list x1 y2) (list x1 y1)) "UCHI_ROAD")
                  (setq id (strcat "VIA-" (itoa (+ 1 c)) "-" (itoa (+ 1 r))))
                  (setq out (append out (list (list id "road" (+ r 1) (+ c 1) x1 y1 x2 y2 area))))
                  (setq areaRoad (+ areaRoad area))
                )
                (progn
                  (if (and (< aporteAcc aporteTarget) (>= front (uchi:subdiv-min-front)))
                    (progn
                      (uchi:draw-polyline-2d (list (list x1 y1) (list x2 y1) (list x2 y2) (list x1 y2) (list x1 y1)) "UCHI_SUBDIV")
                      (setq id (strcat "APORTE-" (itoa (+ 1 c)) "-" (itoa (+ 1 r))))
                      (setq out (append out (list (list id "aporte" (+ r 1) (+ c 1) x1 y1 x2 y2 area))))
                      (setq aporteAcc (+ aporteAcc area))
                      (setq areaAporte (+ areaAporte area))
                    )
                    (if (>= front (uchi:subdiv-min-front))
                      (progn
                        (uchi:draw-polyline-2d (list (list x1 y1) (list x2 y1) (list x2 y2) (list x1 y2) (list x1 y1)) "UCHI_SUBDIV")
                        (setq id (strcat (uchi:subdiv-prefix) "-" (itoa (+ 1 c)) "-" (itoa (+ 1 r))))
                        (setq out (append out (list (list id (if isCorner "lot_corner" "lot") (+ r 1) (+ c 1) x1 y1 x2 y2 area))))
                        (setq cx (/ (+ x1 x2) 2.0) cy (/ (+ y1 y2) 2.0))
                        (uchi:subdiv-annotate (list cx cy) (strcat id " A=" (rtos area 2 1)))
                        (setq lotcount (+ lotcount 1))
                        (setq areaLot (+ areaLot area))
                      )
                    )
                  )
                )
              )
            )
          )
          (setq c (+ c 1))
        )
        (setq r (+ r 1))
      )
      (uchi:subdiv-export-csv out)
      (uchi:subdiv-export-summary areaTot areaLot areaRoad areaAporte)
      (if (> roadn 0) (uchi:subdiv-draw-oriented-road-guides xmin xmax ymin ymax (* dx roadn)))
      (uchi:project-set "subdivision_lots" (length out))
      (uchi:project-set "subdivision_cols" cols)
      (uchi:project-set "subdivision_rows" rows)
      (uchi:project-set "subdivision_ndiv" ndiv)
      (uchi:project-set "subdivision_road_every" roadn)
      (uchi:project-set "subdivision_aporte_pct" (uchi:subdiv-aporte-pct))
      (uchi:project-set "subdivision_annotated_lots" lotcount)
      (uchi:project-save)
      (uchi:log (strcat "Subdivisión generada. Lotes=" (itoa (length out)) ", CSV=uchi_subdivision.csv"))
    )
    (uchi:log "Subdivisión: se requieren al menos 3 puntos.")
  )
  (princ)
)

(princ)
